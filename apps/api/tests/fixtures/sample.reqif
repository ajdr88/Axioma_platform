## R1
- Engine shall provide at least 30,000 lbf takeoff thrust.
- Test

## REQ-SFC-IMPORTED
- Engine shall not exceed the specified cruise fuel consumption rate.
- Analysis

## R3
- Control system shall detect and mitigate turbine overspeed within 50ms.
